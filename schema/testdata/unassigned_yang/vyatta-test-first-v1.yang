module vyatta-test-first-v1 {
	namespace "urn:vyatta.com:test:vyatta-test-first:1";
	prefix first;

	organization "Brocade Communications Systems, Inc.";
	revision 2016-11-04 {
		description "First test schema for configd-schema";
	}

	container first {
		leaf firstLeaf {
			type string;
		}
	}
}
